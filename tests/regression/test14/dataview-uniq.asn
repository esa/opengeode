TASTE-Dataview DEFINITIONS ::=
BEGIN

Int32 ::= INTEGER (-2147483648 .. 2147483647)

Point ::= SEQUENCE {
    x Int32,
    y Int32
}

IntList ::= SEQUENCE (SIZE (2)) OF Int32
VarIntList ::= SEQUENCE (SIZE (2..20)) OF Int32
BoolList ::= SEQUENCE (SIZE (2)) OF BOOLEAN

Nested ::= SEQUENCE {
    a SEQUENCE {
        b SEQUENCE {
            c SEQUENCE {
                p Point,
                l IntList
            }
        }
    }
}

END
