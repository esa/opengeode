TASTE-Dataview DEFINITIONS ::=
BEGIN

Int32 ::= INTEGER (-2147483648 .. 2147483647)

Bool ::= BOOLEAN

Point ::= SEQUENCE {
    x Int32,
    y Int32
}

IntList ::= SEQUENCE (SIZE (2)) OF Int32

VarIntList ::= SEQUENCE (SIZE (1..32)) OF Int32

PointList ::= SEQUENCE (SIZE(2)) OF Point

END
