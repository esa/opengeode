TASTE-BasicTypes DEFINITIONS ::=
BEGIN
T-UInt32 ::= INTEGER (0..4294967295)
TASTE-Peek-id ::= INTEGER (0..4294967295)

TASTE-Peek-id-list ::= SEQUENCE (SIZE (1..10)) OF TASTE-Peek-id
FixedIntList ::= SEQUENCE (SIZE(3)) OF TASTE-Peek-id

MyEnum ::= ENUMERATED {one, two, three, four, five}

MyChoice ::= CHOICE { a BOOLEAN, b ENUMERATED { aa, bb } }

MySeq ::= SEQUENCE { a BOOLEAN, b MyChoice }

END
