TASTE-Dataview DEFINITIONS ::=
BEGIN

Boolean ::= BOOLEAN
Integer ::= INTEGER(-9223372036854775808..9223372036854775807)
Real ::= REAL (-100000000000000000000000000000000000000000000000000000000000000000000000000000000000000000000000000000000000000000000000000000000000000000000000000000000000000000000000000000000000000000000000000000000000000000000000000000000000000000000000000000000000000000000000000000000000000000000000000000000000000000000.0 .. 100000000000000000000000000000000000000000000000000000000000000000000000000000000000000000000000000000000000000000000000000000000000000000000000000000000000000000000000000000000000000000000000000000000000000000000000000000000000000000000000000000000000000000000000000000000000000000000000000000000000000000000.0)
CharString ::= OCTET STRING (SIZE(0..100))

FixSeqof ::= SEQUENCE (SIZE(3)) OF Integer
VarSeqof ::= SEQUENCE (SIZE(0..100)) OF Integer

Seq ::= SEQUENCE {
    i Integer,
    b Boolean,
    f Real,
    s CharString
}

NestedSeq ::= SEQUENCE {
    a SEQUENCE {
        b SEQUENCE {
            c SEQUENCE {
                d Integer
            }
        }
    }
}

BoolSeqOf ::= SEQUENCE (SIZE(4)) OF Boolean

END
