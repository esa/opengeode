TASTE-Dataview DEFINITIONS ::=
BEGIN

EmptySeq ::= SEQUENCE {}
SeqOf ::= SEQUENCE (SIZE(0..10)) OF BOOLEAN

AnotherEmptySeq ::= SEQUENCE {}

NullType ::= NULL

ChoiceWithEmptySeq ::= CHOICE {
  a NULL,
  b EmptySeq,
  c NullType,
  d SEQUENCE { a BOOLEAN }
}

Seq ::= SEQUENCE {
   a ChoiceWithEmptySeq,
   b SeqOf
}

c1 EmptySeq ::= {}

n1 NullType ::= NULL

c2 ChoiceWithEmptySeq ::= a: NULL
c3 ChoiceWithEmptySeq ::= b: {}
c4 ChoiceWithEmptySeq ::= c: NULL
c5 AnotherEmptySeq ::= {}

MyInt ::= INTEGER (-10..10)

-- choice to test the choice_to_int internal operator
Parameters ::= CHOICE {
  one INTEGER (0..255),
  two MyInt,
  three BOOLEAN,
  four-ty-to MyInt
}

-- to test To_Enum and To_Selector
Param-Determinants ::= ENUMERATED { one, two, three, four-ty-to }


-- Type below is accepted by ASN.1 compiler but that's wrong
-- c6 ChoiceWithEmptySeq ::= b: c5


END
