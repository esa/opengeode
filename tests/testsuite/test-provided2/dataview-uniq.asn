TASTE-Dataview DEFINITIONS ::=
BEGIN

T-UInt32 ::= INTEGER (0..100000000)

TC-Type ::= SEQUENCE {
     apid INTEGER (0..100),
     content CHOICE {
         change-mode ENUMERATED { safe, operational },
         patch-memory INTEGER (0..100)
     }
}

TM-Type ::= SEQUENCE {
    apid INTEGER (0..100)
}

Boolean-Type ::= BOOLEAN
END
