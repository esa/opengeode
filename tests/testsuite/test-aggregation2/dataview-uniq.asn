TASTE-Dataview DEFINITIONS ::=


BEGIN

MyChoice ::= CHOICE {
    a CHOICE {
        b CHOICE {
            c BOOLEAN,
            d BOOLEAN
        },
        e BOOLEAN
    },
    f BOOLEAN
}

Some-Thing ::= MyInteger

MyInteger   ::= INTEGER (0..255)

My-OctStr    ::= OCTET STRING (SIZE (0..20))

SeqOf ::= SEQUENCE (SIZE(0..100)) OF MyInteger

Type1 ::= INTEGER(0..1)
Type2 ::= BOOLEAN

Toto ::= SEQUENCE { elem-1 Type1, elem-2 Type2 }

SeqBool ::= SEQUENCE(SIZE(1..5)) OF BOOLEAN

default-seqof SeqOf ::= {4,7,9}
default-str My-OctStr ::= 'DEADBEEF'H

END
