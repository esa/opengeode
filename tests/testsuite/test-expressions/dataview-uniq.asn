TASTE-Dataview DEFINITIONS ::=
BEGIN

Boolean ::= BOOLEAN
MyInteger ::= INTEGER(-9223372036854775808..9223372036854775807)
Real ::= REAL (-100000000000000000000000000000000000000000000000000000000000000000000000000000000000000000000000000000000000000000000000000000000000000000000000000000000000000000000000000000000000000000000000000000000000000000000000000000000000000000000000000000000000000000000000000000000000000000000000000000000000000000000.0 .. 100000000000000000000000000000000000000000000000000000000000000000000000000000000000000000000000000000000000000000000000000000000000000000000000000000000000000000000000000000000000000000000000000000000000000000000000000000000000000000000000000000000000000000000000000000000000000000000000000000000000000000000.0)
CharString ::= IA5String (SIZE (0..100)) -- OCTET STRING (SIZE(0..100))

FixSeqof ::= SEQUENCE (SIZE(3)) OF MyInteger
VarSeqof ::= SEQUENCE (SIZE(0..100)) OF MyInteger
UnsignedInt ::= INTEGER(0..65535)
BiggerUnsigned ::= INTEGER (65537..99999)

Seq ::= SEQUENCE {
    i MyInteger,
    b Boolean,
    f Real,
    s CharString
}

NestedSeq ::= SEQUENCE {
    a SEQUENCE {
        b SEQUENCE {
            c SEQUENCE {
                d MyInteger
            }
        }
    }
}

BoolSeqOf ::= SEQUENCE (SIZE(4)) OF Boolean

END
