TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

END

TASTE-Dataview DEFINITIONS ::=
BEGIN
IMPORTS T-Int32, T-UInt32, T-Int8, T-UInt8, T-Boolean FROM TASTE-BasicTypes;

-- A few simple types to start with ASN.1
MyInteger   ::= T-UInt8

MyReal	    ::= REAL (0.0 .. 1000.0)
LargerReal  ::= REAL (0.0 .. 1000000000)

MyEnum	    ::= ENUMERATED { hello(12), world(13), howareyou(111) }

MySeq	    ::= SEQUENCE {
		    a MyInteger,
		    b ENUMERATED { taste(1), welcomes(2), you(3) }
}

MyChoice    ::= CHOICE {
		    a BOOLEAN,
		    b MySeq
}

MySeqOf	    ::= SEQUENCE (SIZE (2)) OF MyEnum
SeqInt      ::= SEQUENCE (SIZE(1..2)) OF T-UInt8
SeqBool     ::= SEQUENCE (SIZE(2)) OF BOOLEAN
SeqBool2    ::= SEQUENCE (SIZE(1..2)) OF BOOLEAN
MyOctStr    ::= OCTET STRING (SIZE (3))
String      ::= OCTET STRING (SIZE(0..100))

IntSeq ::= SEQUENCE (SIZE(0..100)) OF T-UInt8
FixedIntSeq ::= SEQUENCE (SIZE(5)) OF T-UInt8

-- You can also declare variables (they will be visible in C, Ada and SDL)
myVar	    MySeqOf	::= { hello, world }
END
