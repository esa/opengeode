VEGA DEFINITIONS ::=
BEGIN


IMPORTS T-Int32, T-UInt32, T-Int8, T-UInt8, T-Boolean FROM TASTE-BasicTypes;
-- Used as interface between the GUI and the orchestrator

Simulation-Param ::= SEQUENCE {
  command CHOICE {
      run-n-steps T-UInt32,
      run-n-seconds T-UInt32,
      run-forever BOOLEAN,
      pause BOOLEAN,
      test-gnc BOOLEAN
  },
  gnc-inputs T-GNC-LV-SIM-CONTEXT
}


-- SIMULATOR OUTPUTS / FPS-A INPUTS (cyril's code)
T-GNC-LV-SIM-CONTEXT ::= SEQUENCE {
    attitude-quaternion         T-QUAT-FLOAT32,
    ng-vel-incr-irs             T-VECT3-FLOAT32,
    ng-vel-incr-accelero        T-VECT3-FLOAT32,
    filtered-angles-sample-1    T-VECT3-FLOAT32,
    filtered-angles-sample-2    T-VECT3-FLOAT32
}

-- SIMULATOR INPUTS / FPS-A OUTPUTS (cyril'scode)
T-GNC-LV-SIM-INPUTS ::= SEQUENCE {
    sequ-exec-request-vect   T-HAS-SEQUENCE-EXEC-BEEN-REQUESTED-VECT,
    tvc-set-point-eng-vect  T-TVC-SET-POINT-ENG-VECT,
    racs-ev-cmd-vect        T-RACS-EV-CMD-VECT
}

-- Basic_Types.T_FLOAT32
-- Temporary: set up as double (64 bits) - not sure what range to put for 32 bits
T-FLOAT32 ::= T-DOUBLE -- REAL (-3.40282347e+38..3.40282347e+38)

size-T-QUAT-COMPONENTS INTEGER ::= 4
-- GNC_Types.T_QUAT_FLOAT32
T-QUAT-FLOAT32 ::= SEQUENCE (SIZE(size-T-QUAT-COMPONENTS)) OF T-FLOAT32

size-T-AXIS-3-ID INTEGER ::= 3
T-VECT3-FLOAT32 ::= SEQUENCE (SIZE(size-T-AXIS-3-ID)) OF T-FLOAT32


size-T-SEQUENCE-ID INTEGER ::= 20
T-HAS-SEQUENCE-EXEC-BEEN-REQUESTED-VECT ::= SEQUENCE (SIZE(size-T-SEQUENCE-ID)) OF T-FLOAT32 


size-T-TVC-SET-POINT-ENG-VECT-IDX INTEGER ::= 8
T-TVC-SET-POINT-ENG-VECT ::= SEQUENCE (SIZE(size-T-TVC-SET-POINT-ENG-VECT-IDX)) OF T-FLOAT32


size-T-ACS-EQPT-ID INTEGER ::= 6 
T-RACS-EV-CMD-VECT ::= SEQUENCE (SIZE(size-T-ACS-EQPT-ID)) OF T-FLOAT32 


-- Basic_Types.T_DOUBLE (use double precision - 64 bits)
T-DOUBLE ::= REAL (-100000000000000000000000000000000000000000000000000000000000000000000000000000000000000000000000000000000000000000000000000000000000000000000000000000000000000000000000000000000000000000000000000000000000000000000000000000000000000000000000000000000000000000000000000000000000000000000000000000000000000000000.0 .. 100000000000000000000000000000000000000000000000000000000000000000000000000000000000000000000000000000000000000000000000000000000000000000000000000000000000000000000000000000000000000000000000000000000000000000000000000000000000000000000000000000000000000000000000000000000000000000000000000000000000000000000.0)

-- Types used for the plotting: structure grouping the values to monitor
T-Plot ::= SEQUENCE {
    major-cycle T-UInt32,
    subcycle T-Int8,
    gnc-inputs T-GNC-LV-SIM-CONTEXT,
    gnc-outputs T-GNC-LV-SIM-INPUTS
}



END
TASTE-BasicTypes DEFINITIONS ::=
BEGIN

-- Set of TASTE predefined basic types

T-Int32 ::=  INTEGER (-2147483648 .. 2147483647)

T-UInt32 ::= INTEGER (0 .. 4294967295)

T-Int8 ::= INTEGER (-128 .. 127)

T-UInt8 ::= INTEGER (0 .. 255)

T-Boolean ::= BOOLEAN

END
