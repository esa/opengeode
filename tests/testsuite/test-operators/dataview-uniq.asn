TASTE-Dataview DEFINITIONS ::=
BEGIN

Boolean ::= BOOLEAN
MyInteger ::= INTEGER(-9223372036854775808..9223372036854775807)
Real ::= REAL (-100000000000000000000000000000000000000000000000000000000000000000000000000000000000000000000000000000000000000000000000000000000000000000000000000000000000000000000000000000000000000000000000000000000000000000000000000000000000000000000000000000000000000000000000000000000000000000000000000000000000000000000.0 .. 100000000000000000000000000000000000000000000000000000000000000000000000000000000000000000000000000000000000000000000000000000000000000000000000000000000000000000000000000000000000000000000000000000000000000000000000000000000000000000000000000000000000000000000000000000000000000000000000000000000000000000000.0)
CharString ::= OCTET STRING (SIZE(0..100))

FixSeqof ::= SEQUENCE (SIZE(3)) OF MyInteger
VarSeqof ::= SEQUENCE (SIZE(0..100)) OF MyInteger

Enum-T ::= ENUMERATED { one(12), two(13), three(111) }

Choice ::= CHOICE {
    b BOOLEAN,
    i MyInteger,
    f Real
}

pi Real ::= 3.14159265359

END
