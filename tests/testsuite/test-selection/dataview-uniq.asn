TASTE-Dataview DEFINITIONS ::=
BEGIN

    MyInt ::= INTEGER (0..255)
    MyChoice ::= CHOICE {
        a BOOLEAN,
        b MyInt
    }
   MyDets ::= ENUMERATED { a, b }  -- match the CHOICE options
   MyInt2 ::= INTEGER
   SomeOtherType ::= ENUMERATED {
       a2,
       b2
   }
   

END
