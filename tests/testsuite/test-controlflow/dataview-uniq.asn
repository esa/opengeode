TASTE-Dataview DEFINITIONS ::=
BEGIN

Boolean ::= BOOLEAN
MyInteger ::= INTEGER(-9223372036854775808..9223372036854775807)
Real ::= REAL (-100000000000000000000000000000000000000000000000000000000000000000000000000000000000000000000000000000000000000000000000000000000000000000000000000000000000000000000000000000000000000000000000000000000000000000000000000000000000000000000000000000000000000000000000000000000000000000000000000000000000000000000.0 .. 100000000000000000000000000000000000000000000000000000000000000000000000000000000000000000000000000000000000000000000000000000000000000000000000000000000000000000000000000000000000000000000000000000000000000000000000000000000000000000000000000000000000000000000000000000000000000000000000000000000000000000000.0)

CharString ::= IA5String (SIZE(0..100))
IntegerSeqOf ::= SEQUENCE (SIZE (1..32)) OF MyInteger

END
