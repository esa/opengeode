--
--   Copyright (c) 2015 European Space Agency
--    All Rights Reserved
--
--    Project:    SOIS Electronic Data Sheets
--
--    Module:     Environment_interfaces.asn
--
--    Author:     SOIS EDS Tooling  (internal unreleased version)
--
--


EnvironmentInterfaces DEFINITIONS AUTOMATIC TAGS ::= BEGIN

-- imports
IMPORTS
;



-- interface messages

END
