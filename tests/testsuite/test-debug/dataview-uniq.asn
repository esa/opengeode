TASTE-BasicTypes DEFINITIONS ::=
BEGIN

Boolean ::= BOOLEAN

IaSrtring ::= IA5String (SIZE(0..100))
TASTE-Peek-id ::= INTEGER (0..4294967295)

TASTE-Peek-id-list ::= SEQUENCE (SIZE (1..10)) OF TASTE-Peek-id

VariableString ::= OCTET STRING (SIZE (1..10))
FixedString ::= OCTET STRING (SIZE (5))

IntForRangeCheck ::= INTEGER (0..3)

SeqBool ::= SEQUENCE (SIZE(1..5)) OF BOOLEAN
SeqBoolFix ::= SEQUENCE (SIZE(2)) OF BOOLEAN
SeqEnum ::= SEQUENCE (SIZE(1..5)) OF ENUMERATED { hello2, world2 }
SeqEnumFix ::= SEQUENCE (SIZE(2)) OF ENUMERATED { hello, world }

MyEnum ::= ENUMERATED {a, b, c, d, eE}
MyChoice ::= CHOICE {c1 BOOLEAN, cDe2 BOOLEAN}

SeqOpt ::= SEQUENCE { a BOOLEAN OPTIONAL , b BOOLEAN, c SEQUENCE { a BOOLEAN } OPTIONAL, d OCTET STRING (SIZE (0..10)) OPTIONAL}
SeqNonOpt ::= SEQUENCE { a BOOLEAN }

Enum-With-Values ::= ENUMERATED {foo (4), bar(2)}

-- To test type checks with the Append operator
SeqOf2ElemsOrMore ::= SEQUENCE (SIZE (2..3)) OF INTEGER (5..10)

Boo ::= INTEGER (-10..10)
-- Type to test that a dcl declarations do not refer to any variable
Seq ::= SEQUENCE {
  a Boo,
  b SEQUENCE { foo MyEnum },
  c TASTE-Peek-id-list
}

IaStr ::= IA5String (SIZE(0..50))
OctStr ::= OCTET STRING (SIZE (0..8))
BitStr ::= BIT STRING (SIZE (0..8))

--  Define constants to check the data dictionary
zconst Boo  ::= 5
a-const MyEnum ::= eE
t-const INTEGER ::= 10
uConst MyChoice ::= cDe2: TRUE
iaconst IaStr ::= "Hello"
osconst OctStr ::= 'DEADBEEF'H
bsconst BitStr ::= '01010101'B
seqStr Seq ::= { a 1, b { foo eE }, c {3,14}}

END
