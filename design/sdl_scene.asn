Scene DEFINITIONS ::=
BEGIN

Undefined ::= NULL

QUndoStack ::= NULL

Context ::= ENUMERATED {
    sdl-process,
    sdl-procedure,
    sdl-block,
    statechart,
    lander
}

String ::= IA5String (SIZE (0..255))

Position ::= SEQUENCE {
    x REAL,
    y REAL
}

-- mousePressEvent parameter
QMouseEvent ::= SEQUENCE {
    button ENUMERATED {left, middle, right},
    scenePos Position
}

QKeyEvent ::= SEQUENCE {
}
END
